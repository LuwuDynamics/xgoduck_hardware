import FreeCAD as App
import FreeCADGui as Gui
from pathlib import Path
root=Path(__file__).resolve().parent
doc=App.openDocument(str(root/'Cece_SG90_Ankle_V2.FCStd'))
for ob in doc.Objects:
    if ob.Name.startswith('Left_') or ob.Name.startswith('SG90_Shimming_'):
        ob.ViewObject.Visibility=False
        continue
    ob.ViewObject.Visibility=True
    if ob.Name.endswith('_Leg_V2'):
        ob.ViewObject.ShapeColor=(0.96,0.58,0.16)
    elif ob.Name.endswith('_Foot_Bearing_V2'):
        ob.ViewObject.ShapeColor=(0.16,0.49,0.82)
    elif ob.Name.endswith('_Bearing_Washer'):
        ob.ViewObject.ShapeColor=(0.70,0.73,0.78)
    elif 'SG90_Body_Proxy' in ob.Name:
        ob.ViewObject.ShapeColor=(0.52,0.26,0.72);ob.ViewObject.Transparency=45
    elif 'Turret_Proxy' in ob.Name or 'Shaft_Proxy' in ob.Name:
        ob.ViewObject.ShapeColor=(0.75,0.15,0.16)
    elif 'Tie_Clearance' in ob.Name:
        ob.ViewObject.ShapeColor=(0.15,0.15,0.15);ob.ViewObject.Transparency=50
Gui.activeDocument().activeView().viewAxonometric()
Gui.activeDocument().activeView().fitAll()
Gui.activeDocument().activeView().saveImage(str(root/'Cece_SG90_Ankle_V2_preview.png'),1200,900,'Current')
