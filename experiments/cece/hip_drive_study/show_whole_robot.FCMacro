"""Open the whole feasibility assembly with an exterior view; does not save."""
import FreeCAD as App
import FreeCADGui as Gui
from pathlib import Path
root=Path(__file__).resolve().parent
doc=App.openDocument(str(root/'Cece_Whole_Robot_Leg_Study.FCStd'))
colors={
 'Rounded_Head_Study':(.87,.91,.95),'Rear_Cover_Study':(.8,.87,.93),
 'Body':(.87,.91,.95),'Heart_Frame_V3':(.9,.29,.46),'Antenna':(.97,.7,.29),
 'Left_Arm':(.57,.74,.86),'Right_Arm':(.57,.74,.86),
 'Left_Leg':(.58,.72,.84),'Right_Leg':(.58,.72,.84),
 'Left_Foot':(.35,.53,.71),'Right_Foot':(.35,.53,.71),
 'Left_Washer':(.35,.43,.52),'Right_Washer':(.35,.43,.52),
 'Charger_Tray':(.59,.72,.79),'Charger_Bezel':(.44,.57,.65),
 'OLED_Adafruit4741_Official_CAD':(.1,.15,.22),
 'HC_SR04_Left_Can':(.27,.66,.75),'HC_SR04_Right_Can':(.27,.66,.75),
 'Camera_Lens_Corridor_Provisional':(.1,.12,.16)
}
for o in doc.Objects:
    o.ViewObject.Visibility=o.Name in colors
    if o.Name in colors:
        o.ViewObject.ShapeColor=colors[o.Name]
        o.ViewObject.Transparency=0
        try: o.ViewObject.DisplayMode='Shaded'
        except Exception: pass
Gui.activeDocument().activeView().viewAxonometric()
Gui.activeDocument().activeView().fitAll()
