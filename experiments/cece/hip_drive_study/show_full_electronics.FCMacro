"""Show the full packaging study in FreeCAD with a transparent shell."""
from pathlib import Path
import FreeCAD as App
import FreeCADGui as Gui
root=Path(__file__).resolve().parent
doc=App.openDocument(str(root/'Cece_Full_Electronics_Study.FCStd'))
# Colors identify part locations. Component envelopes are not actual CAD models.
colors={
 'Rounded_Head_Study':((.87,.92,.97),84),'Rear_Cover_Study':((.75,.83,.91),85),
 'Body':((.87,.92,.97),84),'Heart_Frame_V3':((.93,.34,.48),55),
 'Left_Arm':((.55,.73,.86),30),'Right_Arm':((.55,.73,.86),30),
 'Left_Leg':((.57,.72,.85),70),'Right_Leg':((.57,.72,.85),70),
 'Left_Foot':((.36,.53,.72),35),'Right_Foot':((.36,.53,.72),35),
 'Left_Washer':((.4,.45,.5),0),'Right_Washer':((.4,.45,.5),0),
 'Antenna':((1.,.75,.30),0),
 'Charger_Tray':((.55,.75,.80),72),'Charger_Bezel':((.36,.65,.70),65),
 'Charger_UC2_Unpurchased_Proxy':((1.,.42,.1),5),
 'Battery_Clearance':((.3,.76,.35),18),'UBEC_Clearance':((1.,.71,.15),15),
 'OLED_Adafruit4741_Official_CAD':((.08,.2,.34),5),
 'HC_SR04_PCB':((.13,.58,.56),5),'HC_SR04_Left_Can':((.30,.80,.85),5),'HC_SR04_Right_Can':((.30,.80,.85),5),
 'Speaker_COM21311_Clearance':((.89,.22,.48),10),
 'PiicoDev_Driver_Official_Partial_STEP':((.63,.36,.85),3),
 'ESP32_C3_Board_Envelope':((.19,.66,.48),5),
 'DFR0954_Amp_Envelope':((.95,.55,.27),5),'INMP441_Breakout_Envelope':((.27,.58,.92),5),
 'Camera_Stack_Clearance_Provisional':((.17,.75,.50),12),
 'Camera_Lens_Corridor_Provisional':((.08,.10,.13),0),
 'Perfboard_Provisional_30x20':((.52,.32,.13),0),
 'Left_Hip_SG90_Proxy':((.22,.43,.9),12),'Right_Hip_SG90_Proxy':((.22,.43,.9),12),
 'Left_Ankle_SG90_Proxy':((.22,.43,.9),12),'Right_Ankle_SG90_Proxy':((.22,.43,.9),12),
}
for i in range(1,6):colors[f'LED_{i}_Body_Proxy']=((1.,.78,.10),0)
for side in ('Left','Right'):
    for joint in ('Hip','Ankle'):
        colors[f'{side}_{joint}_Turret_Proxy']=((.18,.38,.8),20)
        colors[f'{side}_{joint}_Output_Shaft_Proxy']=((1.,.35,.08),0)
for o in doc.Objects:
    o.ViewObject.Visibility=o.Name in colors
    if o.Name in colors:
        o.ViewObject.ShapeColor,o.ViewObject.Transparency=colors[o.Name]
        try:o.ViewObject.DisplayMode='Shaded'
        except Exception:pass
Gui.activeDocument().activeView().viewAxonometric()
Gui.activeDocument().activeView().fitAll()
