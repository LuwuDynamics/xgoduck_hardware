"""Preview Cece's provisional modifications using the original Otto meshes."""
import FreeCAD as App, Part, Mesh, MeshPart, Draft, os, traceback
from FreeCAD import Vector as V
ROOT=os.path.dirname(os.path.abspath(__file__))
OUT=os.path.join(ROOT,'cece_otto_prototype')
try:
    doc=App.newDocument('Cece_Otto_Prototype')
    group=doc.addObject('App::DocumentObjectGroup','Printed_Parts')
    preview=doc.addObject('App::DocumentObjectGroup','Electronics_References')
    def mesh(name,path,move=(0,0,0),color=(.27,.69,.21)):
        o=doc.addObject('Mesh::Feature',name);o.Label=name.replace('_',' ')
        o.Mesh=Mesh.Mesh(path);o.Placement.Base=V(*move);group.addObject(o)
        o.ViewObject.ShapeColor=color;return o
    def ref(name,shape,color):
        o=doc.addObject('Part::Feature',name);o.Shape=shape;preview.addObject(o);o.Label=name.replace('_',' ');o.ViewObject.ShapeColor=color;return o
    mesh('Body_OLED_window',os.path.join(OUT,'Cece_Otto_Body_OLED_Window.stl'))
    mesh('Head_LED_ports',os.path.join(OUT,'Cece_Otto_Head_LED_Ports.stl'))
    mesh('LED_faceplate',os.path.join(OUT,'Cece_LED_Faceplate.stl'))
    mesh('OLED_bezel',os.path.join(OUT,'Cece_OLED_Retaining_Frame.stl'),(0,-37.5,-19))
    mesh('Left_leg',os.path.join(ROOT,'otto_reference','3Dprint','OttoDIY_Leg_V9.stl'))
    mesh('Right_leg',os.path.join(ROOT,'otto_actual_stl_simulation','assets','leg_mirror.stl'))
    mesh('Left_foot',os.path.join(ROOT,'otto_reference','3Dprint','OttoDIY_foot_V9.stl'))
    mesh('Right_foot',os.path.join(ROOT,'otto_actual_stl_simulation','assets','foot_mirror.stl'))
    ref('OLED_active_area',Part.makeBox(25,0.3,7,V(-12.5,-40.6,-22.5)),(.02,.07,.08))
    batt=ref('Two_AA_holder_allowance',Part.makeBox(59,32,15,V(-29.5,-16,-21.5)),(.3,.3,.3))
    batt.ViewObject.Transparency=65;batt.ViewObject.Visibility=False
    speaker=ref('Speaker_28mm_allowance',Part.makeCylinder(14,4.5,V(0,23.85,14.5),V(0,1,0)),(.3,.3,.3))
    speaker.ViewObject.Transparency=65;speaker.ViewObject.Visibility=False
    for x in (-13.5,13.5):
        ref('Eye_LED_'+str(x).replace('-','L').replace('.','_'),Part.makeCylinder(2.5,1,V(x,-34.6,14.5),V(0,1,0)),(.1,.85,1.0))
    for i,x in enumerate((-5.5,0,5.5)):
        ref('Mouth_LED_%d'%(i+1),Part.makeCylinder(1.5,1,V(x,-34.6,2.4),V(0,1,0)),(1.0,.25,.12))
    # Text on front, above OLED. Separate raised lettering for adhesive/preview.
    label=Draft.make_shapestring(String='Cece',FontFile=r'C:\Windows\Fonts\arialbd.ttf',Size=5,Tracking=0)
    doc.recompute()
    label.Placement=App.Placement(V(-6.6,-34.49,-6.4),App.Rotation(V(1,0,0),90))
    doc.recompute()
    textshape=label.Shape.extrude(V(0,-0.7,0))
    t=doc.addObject('Part::Feature','Cece_Name');t.Shape=textshape;t.Label='Cece name - separate raised letters';group.addObject(t)
    t.ViewObject.ShapeColor=(.93,.92,.78);label.ViewObject.Visibility=False
    MeshPart.meshFromShape(Shape=textshape,LinearDeflection=.05,AngularDeflection=.15,Relative=False).write(os.path.join(OUT,'Cece_Name_Letters.stl'))
    note=doc.addObject('App::FeaturePython','Prototype_Status')
    for key,value in {'Status':'PROTOTYPE - only face and display modifications; head rotation and electronic mounts not complete',
        'Face':'2 x 5 mm LED holes, 3 x 3 mm LED holes, 2.4 mm microphone hole',
        'OLED':'25.6 x 7.6 mm viewing aperture, external 35 x 20 x 4 mm board retainer',
        'Battery':'Provisional ledges for 59 x 32 x 15 mm holder, no retention strap or wiring checks',
        'Speaker':'Rear grille and 28 mm speaker locating rim; mounting clip not yet provided',
        'Original':'Otto DIY v09 from Open-Hardware-Leaders/OttoDIY; local adaptation'} .items():
        note.addProperty('App::PropertyString',key,'Details');setattr(note,key,value)
    doc.recompute();view=Gui.activeDocument().activeView()
    if hasattr(view,'setAnimationEnabled'):view.setAnimationEnabled(False)
    view.viewFront();view.fitAll();Gui.updateGui()
    doc.saveAs(os.path.join(OUT,'Cece_Otto_Prototype.FCStd'))
    view.saveImage(os.path.join(OUT,'cece_otto_preview.png'),1000,1200,'White')
    with open(os.path.join(OUT,'freecad_status.txt'),'w') as f:f.write('SUCCESS')
except Exception:
    with open(os.path.join(OUT,'freecad_status.txt'),'w') as f:f.write(traceback.format_exc())
    raise
